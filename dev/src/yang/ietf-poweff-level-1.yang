module ietf-poweff-level-1 {
  yang-version 1.1;
  namespace "urn:ietf:params:xml:ns:yang:ietf-poweff-level-1";
  prefix ietf-poweff-level-1;

  import ietf-poweff-types {
    prefix ietf-poweff-types;
  }

  organization
    "IETF OPSA (Operations and Management Area) Working Group";
  contact
    "WG Web:   <https://datatracker.ietf.org/wg/opsawg/>
     WG List:  <mailto:opsawg@ietf.org>
     Editor:  Jan Lindblad
              <mailto:jlindbla@cisco.com>
     Editor:  Snezana Mitrovic
              <mailto:snmitrov@cisco.com>
     Editor:  Marisol Palmero
              <mailto:mpalmero@cisco.com>";
  description
    "This YANG module defines the POWEFF Level 1.

    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.
      
    The key words 'MUST', 'MUST NOT', 'REQUIRED', 'SHALL',
    'SHALL NOT', 'SHOULD', 'SHOULD NOT', 'RECOMMENDED',
    'NOT RECOMMENDED', 'MAY', and 'OPTIONAL' in this document
    are to be interpreted as described in BCP 14 (RFC 2119)
    (RFC 8174) when, and only when, they appear in all
    capitals, as shown here.
    ";
  
  revision 2024-04-16 {
    description
      "Initial revision of POWEFF Level 1";
    reference
      "RFC XXXX: ...";
  }

  container poweff {
    description 
      "Top level container for POWEFF.
      ";
    container stats {
      config false;
      description 
        "Statistics (read-only) branch of POWEFF.
        ";
      leaf device-current-total-power-draw {
        type uint32;
        units W;
        ietf-poweff-types:sensor-type 
          ietf-poweff-types:st-p-in-true-watt;
        ietf-poweff-types:tsdb-path 
          poweff.stats.device_current_total_power_draw;
        description 
          "The current power draw of the device that the
          management server pertains to, including power supplies. 
          Does not include power draw of external cooling systems
          that may be required to operate this system.

          The power draw MUST be reported in Watts, and MUST be the
          true RMS power. The reported value MUST NOT be lower than
          the actual power draw. Any violations of these conditions
          may be legally construed as greenwashing, as defined by
          EU Green Claims Directive (GCD), EU 2023/0085(COD).
          ";
      }
    }
  }
}
